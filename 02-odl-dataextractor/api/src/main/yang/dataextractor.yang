module dataextractor {
    yang-version 1;
    namespace "urn:opendaylight:params:xml:ns:yang:dataextractor";
    prefix "dataextractor";

    revision "2015-01-05" {
        description "Initial revision of dataextractor model";
    }
}
